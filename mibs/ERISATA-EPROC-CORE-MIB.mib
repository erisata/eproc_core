ERISATA-EPROC-CORE-MIB DEFINITIONS ::= BEGIN

    IMPORTS
        DisplayString                                   FROM SNMPv2-TC
        Gauge32                                         FROM SNMPv2-SMI
        MODULE-IDENTITY, OBJECT-TYPE                    FROM SNMPv2-SMI
        MODULE-COMPLIANCE, OBJECT-GROUP                 FROM SNMPv2-CONF
        eproc                                           FROM ERISATA-EPROC-MIB
        ;

    eprocCore MODULE-IDENTITY
        LAST-UPDATED "201601070000Z"
        ORGANIZATION "UAB Erisata"
        CONTACT-INFO
            "Karolis Petrauskas
            UAB Erisata
            Vivulskio 15-3, Vilnius
            karolis.petrauskas@erisata.lt"
        DESCRIPTION
            "SNMP module for the EProc Core application."
        REVISION "201601070000Z"
        DESCRIPTION "OID Structure redesigned to simplify it."
        REVISION "201510070000Z"
        DESCRIPTION "Initial revision."
        ::= { eproc 1 }

    --
    --  MIB Conformance objects.
    --
    eprocCoreMib        OBJECT IDENTIFIER ::= { eprocCore 1}
    eprocCoreMibCompls  OBJECT IDENTIFIER ::= { eprocCoreMib 1}
    eprocCoreMibGroups  OBJECT IDENTIFIER ::= { eprocCoreMib 2}

    --
    --  Structure for all metrics.
    --
    eprocCoreObjects    OBJECT IDENTIFIER ::= { eprocCore 2 }



    ----------------------------------------------------------------------------
    --  Object type definitions.
    --

    --
    --  Object types, providing generic information.
    --
    storeModule OBJECT-TYPE
        SYNTAX      DisplayString
        MAX-ACCESS  read-only
        STATUS      current
        DESCRIPTION "Store implementation used by the EProc."
        ::= { eprocCoreObjects 10 }

    registryModule OBJECT-TYPE
        SYNTAX      DisplayString
        MAX-ACCESS  read-only
        STATUS      current
        DESCRIPTION "Registry implementation used by the EProc."
        ::= { eprocCoreObjects 11 }

    limitCount OBJECT-TYPE
        SYNTAX      Gauge32
        MAX-ACCESS  read-only
        STATUS      current
        DESCRIPTION "Number currently maintained limits."
        ::= { eprocCoreObjects 50 }

    --
    --  Object types, providing stats calculated at runtime.
    --  Starts at 100.
    --
    instCreated OBJECT-TYPE
        SYNTAX      Gauge32
        UNITS       "/min"
        MAX-ACCESS  read-only
        STATUS      current
        DESCRIPTION "Number of instances created in last 60 seconds"
        ::= { eprocCoreObjects 100 }

    instStarted OBJECT-TYPE
        SYNTAX      Gauge32
        UNITS       "/min"
        MAX-ACCESS  read-only
        STATUS      current
        DESCRIPTION "Number of instances started in last 60 seconds"
        ::= { eprocCoreObjects 101 }

    instSuspended OBJECT-TYPE
        SYNTAX      Gauge32
        UNITS       "/min"
        MAX-ACCESS  read-only
        STATUS      current
        DESCRIPTION "Number of instances suspended in last 60 seconds"
        ::= { eprocCoreObjects 102 }

    instResumed OBJECT-TYPE
        SYNTAX      Gauge32
        UNITS       "/min"
        MAX-ACCESS  read-only
        STATUS      current
        DESCRIPTION "Number of instances resumed in last 60 seconds"
        ::= { eprocCoreObjects 103 }

    instKilled OBJECT-TYPE
        SYNTAX      Gauge32
        UNITS       "/min"
        MAX-ACCESS  read-only
        STATUS      current
        DESCRIPTION "Number of instances killed in last 60 seconds"
        ::= { eprocCoreObjects 104 }

    instCompleted OBJECT-TYPE
        SYNTAX      Gauge32
        UNITS       "/min"
        MAX-ACCESS  read-only
        STATUS      current
        DESCRIPTION "Number of instances completed in last 60 seconds"
        ::= { eprocCoreObjects 105 }

    instDuration OBJECT-TYPE
        SYNTAX      Gauge32
        UNITS       "s"
        MAX-ACCESS  read-only
        STATUS      current
        DESCRIPTION "
            Total time in seconds spent executing all instances, completed during last 60 seconds.
            TODO: Gauge32 is to small, and this metric is hardly meaningfull.
            "
        ::= { eprocCoreObjects 106 }

    instCrashed OBJECT-TYPE
        SYNTAX      Gauge32
        UNITS       "/min"
        MAX-ACCESS  read-only
        STATUS      current
        DESCRIPTION "Number of FSM instance crashes in last 60 seconds"
        ::= { eprocCoreObjects 107 }

    trnCount OBJECT-TYPE
        SYNTAX      Gauge32
        UNITS       "/min"
        MAX-ACCESS  read-only
        STATUS      current
        DESCRIPTION "Number of transitions, performed in last 60 seconds"
        ::= { eprocCoreObjects 110 }

    trnDuration OBJECT-TYPE
        SYNTAX      Gauge32
        UNITS       "s"
        MAX-ACCESS  read-only
        STATUS      current
        DESCRIPTION "Total time in seconds spent executing all transitions, completed during last 60 seconds"
        ::= { eprocCoreObjects 111 }

    msgInAsyncCount OBJECT-TYPE
        SYNTAX      Gauge32
        UNITS       "/min"
        MAX-ACCESS  read-only
        STATUS      current
        DESCRIPTION "Number of async messages handled by FSMs in last 60 seconds"
        ::= { eprocCoreObjects 120 }

    msgInSyncCount OBJECT-TYPE
        SYNTAX      Gauge32
        UNITS       "/min"
        MAX-ACCESS  read-only
        STATUS      current
        DESCRIPTION "Number of sync messages handled by FSMs in last 60 seconds"
        ::= { eprocCoreObjects 121 }

    msgOutAsyncCount OBJECT-TYPE
        SYNTAX      Gauge32
        UNITS       "/min"
        MAX-ACCESS  read-only
        STATUS      current
        DESCRIPTION "Number of async messages sent by FSMs in last 60 seconds"
        ::= { eprocCoreObjects 122 }

    msgOutSyncCount OBJECT-TYPE
        SYNTAX      Gauge32
        UNITS       "/min"
        MAX-ACCESS  read-only
        STATUS      current
        DESCRIPTION "Number of sync messages sent by FSMs in last 60 seconds"
        ::= { eprocCoreObjects 123 }


    --
    --  Store performance stats.
    --  Starts at 200.
    --
    storeGetInstance OBJECT-TYPE
        SYNTAX      Gauge32
        UNITS       "us"
        MAX-ACCESS  read-only
        STATUS      current
        DESCRIPTION "Mean duration in us of the corresponding eproc_store operation."
        ::= { eprocCoreObjects 201 }

    storeGetTransition OBJECT-TYPE
        SYNTAX      Gauge32
        UNITS       "us"
        MAX-ACCESS  read-only
        STATUS      current
        DESCRIPTION "Mean duration in us of the corresponding eproc_store operation."
        ::= { eprocCoreObjects 202 }

    storeGetState OBJECT-TYPE
        SYNTAX      Gauge32
        UNITS       "us"
        MAX-ACCESS  read-only
        STATUS      current
        DESCRIPTION "Mean duration in us of the corresponding eproc_store operation."
        ::= { eprocCoreObjects 203 }

    storeGetMessage OBJECT-TYPE
        SYNTAX      Gauge32
        UNITS       "us"
        MAX-ACCESS  read-only
        STATUS      current
        DESCRIPTION "Mean duration in us of the corresponding eproc_store operation."
        ::= { eprocCoreObjects 204 }

    storeGetNode OBJECT-TYPE
        SYNTAX      Gauge32
        UNITS       "us"
        MAX-ACCESS  read-only
        STATUS      current
        DESCRIPTION "Mean duration in us of the corresponding eproc_store operation."
        ::= { eprocCoreObjects 205 }

    storeAddInstance OBJECT-TYPE
        SYNTAX      Gauge32
        UNITS       "us"
        MAX-ACCESS  read-only
        STATUS      current
        DESCRIPTION "Mean duration in us of the corresponding eproc_store operation."
        ::= { eprocCoreObjects 206 }

    storeAddTransition OBJECT-TYPE
        SYNTAX      Gauge32
        UNITS       "us"
        MAX-ACCESS  read-only
        STATUS      current
        DESCRIPTION "Mean duration in us of the corresponding eproc_store operation."
        ::= { eprocCoreObjects 207 }

    storeSetInstanceKilled OBJECT-TYPE
        SYNTAX      Gauge32
        UNITS       "us"
        MAX-ACCESS  read-only
        STATUS      current
        DESCRIPTION "Mean duration in us of the corresponding eproc_store operation."
        ::= { eprocCoreObjects 208 }

    storeSetInstanceSuspended OBJECT-TYPE
        SYNTAX      Gauge32
        UNITS       "us"
        MAX-ACCESS  read-only
        STATUS      current
        DESCRIPTION "Mean duration in us of the corresponding eproc_store operation."
        ::= { eprocCoreObjects 209 }

    storeSetInstanceResuming OBJECT-TYPE
        SYNTAX      Gauge32
        UNITS       "us"
        MAX-ACCESS  read-only
        STATUS      current
        DESCRIPTION "Mean duration in us of the corresponding eproc_store operation."
        ::= { eprocCoreObjects 210 }

    storeSetInstanceResumed OBJECT-TYPE
        SYNTAX      Gauge32
        UNITS       "us"
        MAX-ACCESS  read-only
        STATUS      current
        DESCRIPTION "Mean duration in us of the corresponding eproc_store operation."
        ::= { eprocCoreObjects 211 }

    storeAddInstCrash OBJECT-TYPE
        SYNTAX      Gauge32
        UNITS       "us"
        MAX-ACCESS  read-only
        STATUS      current
        DESCRIPTION "Mean duration in us of the corresponding eproc_store operation."
        ::= { eprocCoreObjects 212 }

    storeLoadInstance OBJECT-TYPE
        SYNTAX      Gauge32
        UNITS       "us"
        MAX-ACCESS  read-only
        STATUS      current
        DESCRIPTION "Mean duration in us of the corresponding eproc_store operation."
        ::= { eprocCoreObjects 213 }

    storeLoadRunning OBJECT-TYPE
        SYNTAX      Gauge32
        UNITS       "us"
        MAX-ACCESS  read-only
        STATUS      current
        DESCRIPTION "Mean duration in us of the corresponding eproc_store operation."
        ::= { eprocCoreObjects 214 }

    storeAttrTask OBJECT-TYPE
        SYNTAX      Gauge32
        UNITS       "us"
        MAX-ACCESS  read-only
        STATUS      current
        DESCRIPTION "Mean duration in us of the corresponding eproc_store operation."
        ::= { eprocCoreObjects 215 }

    storeAttachmentSave OBJECT-TYPE
        SYNTAX      Gauge32
        UNITS       "us"
        MAX-ACCESS  read-only
        STATUS      current
        DESCRIPTION "Mean duration in us of the corresponding eproc_store operation."
        ::= { eprocCoreObjects 216 }

    storeAttachmentRead OBJECT-TYPE
        SYNTAX      Gauge32
        UNITS       "us"
        MAX-ACCESS  read-only
        STATUS      current
        DESCRIPTION "Mean duration in us of the corresponding eproc_store operation."
        ::= { eprocCoreObjects 217 }

    storeAttachmentDelete OBJECT-TYPE
        SYNTAX      Gauge32
        UNITS       "us"
        MAX-ACCESS  read-only
        STATUS      current
        DESCRIPTION "Mean duration in us of the corresponding eproc_store operation."
        ::= { eprocCoreObjects 218 }

    storeAttachmentCleanup OBJECT-TYPE
        SYNTAX      Gauge32
        UNITS       "us"
        MAX-ACCESS  read-only
        STATUS      current
        DESCRIPTION "Mean duration in us of the corresponding eproc_store operation."
        ::= { eprocCoreObjects 219 }



    ----------------------------------------------------------------------------
    --  MIB Conformance definitions.
    --

    eprocCoreMibComplBasic MODULE-COMPLIANCE
        STATUS current
        DESCRIPTION
            "The basic compliance statement for SNMPv2 entities
            which implement the ERISATA-EPROC-CORE-MIB."
        MODULE
            MANDATORY-GROUPS {
                eprocCoreGenericOG,
                eprocCoreRTStatsOG,
                eprocCoreStoreStatsOG
            }
            GROUP eprocCoreGenericOG
            DESCRIPTION "This group is mandatory."
            GROUP eprocCoreRTStatsOG
            DESCRIPTION "This group is mandatory."
            GROUP eprocCoreStoreStatsOG
            DESCRIPTION "This group is mandatory."
        ::= { eprocCoreMibCompls 1 }


    eprocCoreGenericOG OBJECT-GROUP
        OBJECTS {
            storeModule,
            registryModule,
            limitCount
        }
        STATUS current
        DESCRIPTION "Generic EProc information."
        ::= { eprocCoreMibGroups 1 }

    eprocCoreRTStatsOG OBJECT-GROUP
        OBJECTS {
            instCreated,
            instStarted,
            instSuspended,
            instResumed,
            instKilled,
            instCompleted,
            instDuration,
            instCrashed,
            trnCount,
            trnDuration,
            msgInAsyncCount,
            msgInSyncCount,
            msgOutAsyncCount,
            msgOutSyncCount
        }
        STATUS current
        DESCRIPTION "Statistics collected at runtime."
        ::= { eprocCoreMibGroups 2 }

    eprocCoreStoreStatsOG OBJECT-GROUP
        OBJECTS {
            storeGetInstance,
            storeGetTransition,
            storeGetState,
            storeGetMessage,
            storeGetNode,
            storeAddInstance,
            storeAddTransition,
            storeSetInstanceKilled,
            storeSetInstanceSuspended,
            storeSetInstanceResuming,
            storeSetInstanceResumed,
            storeAddInstCrash,
            storeLoadInstance,
            storeLoadRunning,
            storeAttrTask,
            storeAttachmentSave,
            storeAttachmentRead,
            storeAttachmentDelete,
            storeAttachmentCleanup
        }
        STATUS current
        DESCRIPTION "Store performance stats."
        ::= { eprocCoreMibGroups 3 }



END
